module securris {

  namespace "http://www.nic.cz/ns/router/securris";

  prefix "securris";

  import ietf-inet-types {
    prefix "inet";
  }

  organization
    "CZ.NIC, z. s. p. o.";

  contact
    "Ladislav Lhotka <mailto:lhotka@nic.cz>";

  description
    "This YANG module defines the data model for Turris smart home
     gateway.";

  revision 2015-03-02 {
    description
      "Initial revision.";
  }

  /* Identities */

  identity device-type {
    description
      "Base identity from which specific device types are derived.";
  }

  identity global-device {
    base device-type;
    description
      "Base identity from which global device types are derived.";
  }

  identity section-device {
    base device-type;
    description
      "Base identity from which section-wise device types are
       derived.";
  }

  identity siren {
    base global-device;
    description
      "Siren device.";
  }

  identity relay {
    base global-device;
    description
      "Relay device.";
  }

  identity key-fob {
    base section-device;
    description
      "Remote controller.";
  }

  identity PIR {
    base section-device;
    description
      "Passive infrared sensor.";
  }

  identity door-sensor {
    base section-device;
    description
      "Magnetic door sensor.";
  }

  identity smoke-detector {
    base section-device;
    description
      "Smoke detector.";
  }

  /* Typedefs */

  typedef email-address {
    type string {
      pattern "[\\-_.a-zA-Z0-9]+@[\\-_.a-zA-Z0-9]+(\\.[\\-_.a-zA-Z0-9]+)*";
    }
    description
      "Valid format of an email address.";
  }

  typedef phone-number {
    type string {
      pattern "\\+?[0-9]+(-[0-9]+)*";
    }
    description
      "Valid format of a phone number.";
  }

  typedef event {
    type enumeration {
      enum default {
        value "0";
        description
          "unspecified event";
      }
      enum alarm {
        value "1";
        description
          "alarm event";
      }
      enum arm {
        value "2";
        description
          "arm/disarm event";
      }
      enum button {
        value "3";
        description
          "button-pressed event";
      }
      enum defect {
        value "4";
        description
          "defect event";
      }
      enum low-battery {
        value "5";
        description
          "low-battery event";
      }
      enum panic {
        value "6";
        description
          "panic event";
      }
      enum sensor-lost {
        value "7";
        description
          "sensor-lost event";
      }
      enum tamper {
        value "8";
        description
          "tamper event";
      }
    }
  }

  /* Groupings */

  grouping description {
    leaf description {
      type string;
      description
        "Textual description of an object.";
    }
  }

  grouping common-device-pars {
    description
      "Common device parameters";
    leaf id {
      type string {
        pattern "[0-9]{1,8}";
      }
      description
        "Identifier of the device.";
    }
    uses description;
    leaf lost-after {
      type uint32;
      units "seconds";
      default "300";
      description
        "The time interval after receiving the last beacon when the
         device is considered dead.

         Value of 0 means that the device sends no beacons.";
    }
  }

  /* Configuration data */

  container securris {
    description
      "Securris gateway configuration.";
    container global {
      description
        "Global configuration.";
      leaf dump-target {
        type inet:uri;
        default "file:///tmp/securris-dump.log";
        description
          "Location for dumps.";
      }
      list device {
        key "id";
        description
          "The list of global (non-section) devices.";
        uses common-device-pars;
        leaf type {
          type identityref {
            base global-device;
          }
          mandatory "true";
          description
            "Type of the global device.";
        }
      }
    }
    list section {
      key "name";
      description
        "The list of configured sections.";
      leaf name {
        type string;
        description
          "Unique name of the section.";
      }
      uses description;
      list event-actions {
        key "event";
        description
          "Configuration of actions to be performed in response to
           events.

           If the 'default' event is configured, then its actions are
           used as the default for events that are not explicitly
           configured.";
        leaf event {
          type event;
          description
            "The event for which actions are configured.";
        }
        leaf ignore {
          type boolean;
          default "false";
          description
            "If this flag is set to true, the event is ignored in
             within the section even if other actions are
             configured.";
        }
        leaf-list activate {
          type leafref {
            path "/securris/global/device/id";
          }
          description
            "List of global devices to activate in response to the
             event.";
        }
        leaf mail {
          type email-address;
          description
            "Send an email in response to the event.";
        }
        leaf sms {
          type phone-number;
          description
            "Send a text message in response to the event.";
        }
        leaf command {
          type string;
          description
            "Execute a shell command in response to the event.

             The value is is a complete command with parameters.";
        }
      }
      list device {
        key "id";
        description
          "The list of devices in the zone.";
        uses common-device-pars;
        leaf type {
          type identityref {
            base section-device;
          }
          mandatory "true";
          description
            "Type of the section device.";
        }
        leaf delay {
          type uint32;
          units "seconds";
          default "0";
          description
            "Delay before activation.";
        }
        leaf-list confirm {
          type leafref {
            path "../../device/id";
          }
          must "not(. = ../id)" {
            error-message "Self-confirmation is not allowed.";
          }
          description
            "The list of devices that need to confirm an alarm.";
        }
        leaf-list ignore-events {
          type event;
          description
            "List of events generated by the device that are to be
             ignored.";
        }
      }
    }
  }
}
