submodule bird-nest {

  belongs-to bird {
    prefix "bird";
  }

  import ietf-yang-types {
    prefix "yang";
  }

  import ietf-routing {
    prefix "rt";
  }

  description
    "This module defines configuration data, RPCs and features that
     are common to all routing protocols.";

  /* Features */

  feature mrtdump {
    description
      "Indicates support for MRTdump.";
  }

  feature route-origin {
    description
      "Indicates operating system support for identification of route
       origin.";
  }

  /* Groupings */

  grouping universal-route-attributes {
    description
      "Set of universal (protocol-idenpendent) route attributes.";
    leaf filtered {
      type boolean;
      description
        "This flag is used for indicating that the parent route
         didn't pass the import filter. Depending on the setting of
         the protocol option 'import-keep-filtered', filtered routes
         may be discarded or retained but labeled as filtered using
         this attribute.";
    }
  }

  grouping protocol-debugging {
    description
      "Protocol debugging options.

       This grouping is used in global and protocol configuration.";
    choice protocol-debugging-options {
      description
        "Select all or none, or an explicit list of debug types.";
      default "none";
      leaf none {
        type empty;
        description
          "No debugging. This is the default.";
      }
      leaf all {
        type empty;
        description
          "Turn on all types of debugging.";
      }
      leaf-list type {
        description
          "Each entry turns on one type of debug messages.";
        type enumeration {
          enum states {
            description
              "protocol state changes";
          }
          enum routes {
            description
              "routes exchanged with the connected RIB";
          }
          enum filters {
            description
              "route filtering";
          }
          enum interfaces {
            description
              "protocol-related events on interfaces";
          }
          enum events {
            description
              "protocol's internal events";
          }
          enum packets {
            description
              "protocol packets (sent and received)";
          }
        }
      }
    }
  }

  grouping mrtdump {
    description
      "MRTdump options.

       This grouping is used in global and protocol configuration.";
    choice mrtdump-options {
      description
        "Select all or none, or an explicit list of MRTdump types.";
      default "none";
      leaf none {
        type empty;
        description
          "No MRTdump messages. This is the default.";
      }
      leaf all {
        type empty;
        description
          "Turn on all types of MRTdump messages.";
      }
      leaf-list type {
        description
          "Each entry turns on one type of MRTdump messages.";
        type enumeration {
          enum states {
            description
              "state changes";
          }
          enum messages {
            description
              "protocol messages";
          }
        }
      }
    }
  }

  grouping common-protocol-data {
    description
      "Common configuration parameters of BIRD protocols.";
    grouping protocol-route-limit {
      description
        "Common configuration data for route limits.";
      leaf limit {
        type uint32;
        mandatory "true";
        description
          "Maximum number of routes";
      }
      leaf action {
        type enumeration {
          enum warn {
            description
              "Print a warning log message.";
          }
          enum block {
            description
              "Discard excessive routes.";
          }
          enum restart {
            description
              "Restart the routing protocol instance.";
          }
          enum disable {
            description
              "Disable the routing protocol instance.";
          }
        }
        default "disable";
        description
          "Action to perform if the limit is reached.";
      }
    }
    leaf rib {
      type leafref {
        path "../../../rt:ribs/rt:rib/rt:name";
      }
      description
        "The RIB to which the routing protocol instance is connected.

         If this leaf is not present, the protocol instance is
         connected to the default RIB.";
    }
    container debug {
      description
        "Protocol debugging options.";
      uses protocol-debugging;
    }
    container mrtdump {
      if-feature mrtdump;
      description
        "MRTdump options.";
      uses mrtdump;
    }
    leaf import-keep-filtered {
      type boolean;
      default "false";
      description
        "This flag controls whether filtered routes are discarded or
         just labeled as filtered (using the 'filtered' route
         attribute) and kept in the protocol routing table.";
    }
    container import-limit {
      presence "Set the import limit";
      description
        "Maximum number of imported routes.

         If the 'import-keep-filtered' flag is true, the routes with
         the 'filtered' attribute are not counted towards this
         limit.";
      uses protocol-route-limit;
    }
    container receive-limit {
      presence "Set the receive limit";
      description
        "Maximum number of received routes.

         If the 'import-keep-filtered' flag is true, the routes with
         the 'filtered' attribute are counted towards this limit.";
      uses protocol-route-limit;
    }
    container export-limit {
      presence "Set the export limit";
      description
        "Maximum number of exported routes.

         If the 'import-keep-filtered' flag is true, the routes with
         the 'filtered' attribute are counted towards this limit.";
      uses protocol-route-limit;
    }
  }

  grouping protocol-interfaces {
    description
      "This grouping is used in the configuration of routing protocol
       instances.";
    container interfaces {
      description
        "Configuration of router interfaces participating in the
         routing protocol instance.";
      list interface {
        key "name";
        leaf name {
          type leafref {
            path
              "../../../../../rt:interfaces/rt:interface/rt:name";
          }
        }
      }
    }
  }

  grouping rip-ospf-passwords {
    description
      "Password configuration options for RIP and OSPF protocols.

       If multiple passwords are configured, it is up to the protocol
       implementation to decide which one is used.

       Configuring one or more passwords doesn't automatically mean
       that they are really used. Authentication has to be enabled
       separately using the protocol-specific 'authentication'
       parameter.";
    container passwords {
      description
        "Configured passwords.";
      list password {
        key "id";
        description
          "Password entry.";
        leaf id {
          type uint8;
          description
            "Unique identifier of the password entry.

             Some protocols use this value for identifying the
             password that is used for authenticating protocol
             packets.";
        }
        leaf text {
          type string;
          mandatory "true";
          description
            "The password in clear text.";
        }
        leaf generate-from {
          type yang:date-and-time;
          description
            "Start of the time interval in which the password may be
             used for packet signing.";
        }
        leaf generate-to {
          type yang:date-and-time;
          description
            "End of the time interval in which the password may be
             used for packet signing.";
        }
        leaf accept-from {
          type yang:date-and-time;
          description
            "Start of the time interval in which the password may be
             used for packet verification.";
        }
        leaf accept-to {
          type yang:date-and-time;
          description
            "End of the time interval in which the password may be
             used for packet verification.";
        }
      }
    }
  }

  /* RPC methods */

  augment "/rt:fib-route/rt:output/rt:route" {
    description
      "Add universal route attributes.";
    uses universal-route-attributes;
  }

  rpc reload {
    description
      "Reload the specified protocol instance(s). The result of the
       reload operation is that routes are reimported from the
       protocol instance and/or active routes are reexported to the
       protocol instance.";
    input {
      leaf router {
        type rt:routing-instance-state-ref;
        mandatory "true";
        description
          "The name of a router instance. The protocol instances to
           be reloaded must all reside in this router.";
      }
      leaf direction {
        type enumeration {
          enum in;
          enum out;
          enum both;
        }
        default "both";
        description
          "Control the direction in which the routes are resent
           during the reload:

           - 'in': reimport the routes from each protocol instance to
             the connected RIB;

           - 'out': reexport the active routes from the connected RIB
             to the protocol instance;

           - 'both' (default): perform both 'in' and 'out'.";
      }
      container protocol-instances {
        presence "explicit protocol selection";
        description
          "If this container is present, only the listed protocol
           instances are reloaded. Otherwise, all protocol instances
           in the router are reloaded.";
        leaf-list protocol-instance {
          type leafref {
            path "/rt:routing/rt:routing-instance/"
               + "rt:routing-protocols/rt:routing-protocol/rt:name";
          }
          description
            "The names of the protocols to be reloaded.";
        }
      }
    }
  }

  /* Data nodes */

  augment "/rt:routing/rt:routing-instance/rt:routing-protocols/"
        + "rt:routing-protocol" {
    uses common-protocol-data;
  }

  augment "/rt:routing-state/rt:routing-instance/rt:ribs/rt:rib/"
        + "rt:routes/rt:route" {
    description
      "Add universal route attributes.";
    uses universal-route-attributes;
  }

  augment "/rt:routing/rt:routing-instance/bird:bird-config" {
    if-feature mrtdump;
    container mrtdump {
      description
        "Global MRTdump configuration.";
      presence "enable mrtdump";
      leaf enabled {
        type boolean;
        default "true";
        description
          "Enable MRTdump.";
      }
      leaf file {
        type string;
        mandatory "true";
        description
          "Name of the file for storing MRTdump messages.";
      }
      container global-options {
        description
          "Global MRTdump options.";
        uses mrtdump;
      }
    }
    container bgp-listen {
      description
        "Configure the listening socket for all BGP instances.";
      /* TODO */
    }
  }

  augment "/rt:routing/rt:routing-instance/bird:bird-config/"
        + "bird:debugging" {
    container protocols {
      description
        "Global protocol debugging configuration.";
      container global-options {
        description
          "Global protocol debugging options.";
        uses protocol-debugging;
      }
    }
  }
}
