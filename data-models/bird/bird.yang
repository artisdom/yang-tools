module bird {

  namespace "http://www.nic.cz/ns/bird";

  prefix "bird";

  import ietf-routing {
    prefix "rt";
  }

  include bird-global;

  include bird-device;

  include bird-kernel;

  include bird-nest;

  /*
  <include module="bird-rip"/>
  <include module="bird-ospf"/>
  <include module="bird-bgp"/>
  */

  organization
    "CZ.NIC, z. s. p. o.";

  contact
    "Ladislav Lhotka <mailto:lhotka@nic.cz>";

  reference
    "http://bird.network.cz/?get_doc&f=bird.html";

  description
    "Configuration of the BIRD Internet Routing Daemon.";

  revision 2012-10-09 {
    description
      "Initial revision.";
  }

  /* Identities */

  identity bird-daemon {
    base rt:routing-instance;
  }

  identity bird-ipv4 {
    base bird-daemon;
    description
      "This identity represents BIRD routing daemon compiled with
       support for IPv4 routing.";
  }

  identity bird-ipv6 {
    base bird-daemon;
    description
      "This identity represents BIRD routing daemon compiled with
       support for IPv6 routing.";
  }

  /* RPC Methods */

  rpc shutdown {
    description
      "Shut BIRD down.";
    input {
      leaf router {
        type rt:routing-instance-state-ref;
        description
          "The name of the routing instance to be shut down.";
      }
    }
  }
}
